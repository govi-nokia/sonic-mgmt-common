module openconfig-lldp-annot {

    yang-version "1";

    namespace "http://openconfig.net/yang/annotation/oc-lldp-annot";
    prefix "oc-lldp-annot";

    import sonic-extensions { prefix sonic-ext; }
    import openconfig-lldp { prefix oc-lldp; }

    organization
        "SONiC";

    contact
        "SONiC";

    description
        "OpenConfig LLDP YANG annotations for SONiC transformer framework.";

    revision 2026-09-05 {
        description
            "OpenConfig LLDP 1.2.0: map global custom-tlvs from CONFIG_DB
            LLDP_CUSTOM_TLV; keep per-interface custom-tlv-names
            not-supported; map /lldp/mgmt-addresses from LLDP_LOC_CHASSIS;
            map state counters from COUNTERS_DB LLDP_STATISTICS.";
    }

    revision 2026-07-03 {
        description
            "Initial revision: map LLDP interfaces/neighbors to APPL_DB LLDP_ENTRY_TABLE.";
    }

    revision 2026-07-03-2 {
        description
            "Add global config/state and per-interface config mappings.";
    }

    revision 2026-07-30 {
        description
            "Add field transformers for global system-info leaves so leaf GET
            applies the same LLDP_LOC_CHASSIS fallback as container GET.";
    }

    deviation /oc-lldp:lldp/oc-lldp:config {
        deviate add {
            sonic-ext:db-name "CONFIG_DB";
            sonic-ext:subtree-transformer "lldp_config_xfmr";
        }
    }

    deviation /oc-lldp:lldp/oc-lldp:state {
        deviate add {
            sonic-ext:subtree-transformer "lldp_state_xfmr";
        }
    }

    deviation /oc-lldp:lldp/oc-lldp:interfaces {
        deviate add {
            sonic-ext:subtree-transformer "lldp_interfaces_xfmr";
        }
    }

    deviation /oc-lldp:lldp/oc-lldp:mgmt-addresses {
        deviate add {
            sonic-ext:subtree-transformer "lldp_mgmt_addresses_xfmr";
        }
    }

    // Global custom-tlvs is config true in 1.2.0.
    // custom-tlv-names leafrefs this list but lldpd custom TLVs are global only.
    deviation /oc-lldp:lldp/oc-lldp:custom-tlvs {
        deviate add {
            sonic-ext:db-name "CONFIG_DB";
            sonic-ext:subtree-transformer "lldp_custom_tlvs_xfmr";
        }
    }

    deviation /oc-lldp:lldp/oc-lldp:interfaces/oc-lldp:interface/oc-lldp:config/oc-lldp:custom-tlv-names {
        deviate not-supported;
    }

    deviation /oc-lldp:lldp/oc-lldp:interfaces/oc-lldp:interface/oc-lldp:state/oc-lldp:custom-tlv-names {
        deviate not-supported;
    }

    deviation /oc-lldp:lldp/oc-lldp:config/oc-lldp:system-name {
        deviate add {
            sonic-ext:field-transformer "lldp_system_name_fld_xfmr";
        }
    }

    deviation /oc-lldp:lldp/oc-lldp:config/oc-lldp:system-description {
        deviate add {
            sonic-ext:field-transformer "lldp_system_description_fld_xfmr";
        }
    }

    deviation /oc-lldp:lldp/oc-lldp:config/oc-lldp:chassis-id {
        deviate add {
            sonic-ext:field-transformer "lldp_chassis_id_fld_xfmr";
        }
    }

    deviation /oc-lldp:lldp/oc-lldp:config/oc-lldp:chassis-id-type {
        deviate add {
            sonic-ext:field-transformer "lldp_chassis_id_type_fld_xfmr";
        }
    }

    deviation /oc-lldp:lldp/oc-lldp:state/oc-lldp:system-name {
        deviate add {
            sonic-ext:field-transformer "lldp_system_name_fld_xfmr";
        }
    }

    deviation /oc-lldp:lldp/oc-lldp:state/oc-lldp:system-description {
        deviate add {
            sonic-ext:field-transformer "lldp_system_description_fld_xfmr";
        }
    }

    deviation /oc-lldp:lldp/oc-lldp:state/oc-lldp:chassis-id {
        deviate add {
            sonic-ext:field-transformer "lldp_chassis_id_fld_xfmr";
        }
    }

    deviation /oc-lldp:lldp/oc-lldp:state/oc-lldp:chassis-id-type {
        deviate add {
            sonic-ext:field-transformer "lldp_chassis_id_type_fld_xfmr";
        }
    }
}
